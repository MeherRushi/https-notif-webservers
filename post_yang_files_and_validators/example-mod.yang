module example-mod {
  yang-version 1.1;
  namespace "https://example.com/example-mod";
  prefix emod;

  organization "Example Organization";
  contact "support@example.com";

  description
    "Example module for event details.";

  revision 2024-06-17 {
    description "First revision.";
  }

  grouping event {
    description "Details of the event.";

    container event {
      leaf event-class {
        type string;
        description "Class of the event, e.g., fault or alarm.";
      }

      container reporting-entity {
        leaf card {
          type string;
          description "The specific card or interface reporting the event.";
        }
      }

      leaf severity {
        type string;
        description "Severity level of the event, e.g., major, minor, critical.";
      }
    }
  }
}
